{
"TOSHIBA",  "LED TV", "55", "QUARD CORE", "3", "2"
}
    
TV ::= SEQUENCE
{
     brand IA5String,
     display-type IA5String,
     size-inches INTEGER,
     processor IA5String,
     bluetooth BOOLEAN DEFAULT TRUE,
     wi-fi BOOLEAN TRUE,
     number-of-HDMI INTEGER
},
     color ENUMERATED
{
      black (0),
      gray(1),
      white(2)
}

END
